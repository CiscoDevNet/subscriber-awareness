module subawa {
    yang-version 1;
    namespace "urn:opendaylight:params:xml:ns:yang:subawa";
    prefix "subawa";

    revision "2015-01-05" {
        description "Initial revision of subawa model";
    }

    import ietf-inet-types { prefix inet; revision-date "2013-07-15"; }
    import ietf-yang-types { prefix yang; revision-date "2013-07-15"; }





    container subscriber-flow-info {
        list subscriber-flow-info-entry {
            description
                "List of all subscriber-flow database instances.";
            key "subId";
            leaf subId{
                type uint32;
            }
	        list flow-features{
		        key "id";
		        leaf id {
		            type uint32;
		        }
                leaf Ip-Src {
                    type inet:ip-prefix;
                }
                leaf Ip-Dst {
                    type inet:ip-prefix;
                }
                leaf Port-Src {
                    type inet:port-number;
                }
                leaf Port-Dst {
                    type inet:port-number;
                }
                leaf Ip-Version {
                    type inet:ip-version;
                }
	            leaf Ip-Protocol {
	                type enumeration {
	    	            enum "TCP" {
		                    value 6;
		                    description "TCP Protocol";
		            }
		                enum "UDP" {
		                    value 17;
		                    description "UDP Protocol";
		                }
	                }
	            }
		        leaf Time-Out {
		            type uint32;
		        }
	        }
        }
    }

    container nodes-subscriber-info {
	    list node {
	        key "nodeId";
	        leaf nodeId {
		        type string;
	        }
	        list subscriber {
		        key "subId";
		        leaf subId {
		            type uint32;
		        }
		        list flow-features{
		            key "id";
		            leaf id {
			            type uint32;
		            }
                    leaf Ip-Src {
                        type inet:ip-prefix;
                    }
                    leaf Ip-Dst {
                        type inet:ip-prefix;
                    }
                    leaf Port-Src {
                        type inet:port-number;
                    }
                    leaf Port-Dst {
                        type inet:port-number;
                    }
                    leaf Ip-Version {
                        type inet:ip-version;
                    }
	                leaf Ip-Protocol {
	                    type enumeration {
	    	                enum "TCP" {
		                        value 6;
		                        description "TCP Protocol";
		                    }
		                    enum "UDP" {
		                        value 17;
		                        description "UDP Protocol";
		                    }
	                    }
	                }
		            leaf count {
			            type uint32;
		            }
		        }
	        }
	    }

    }

    container subscriber-basic-info {
        list subscriber-basic-info-entry {
            description
                "List of all subscriber-basic database instances.";
            key "subId";
            leaf subId{
                type uint32;
            }
            leaf fname {
                type string;
            }
            leaf lname {
                type string;
            }
            leaf address {
                type string;
            }

        }
    }



    rpc register-subscriber-flow-info {
        description "Register subscriber Id and the flow information";
        input {
            leaf subId {
                type uint32 {
                    range "1 .. 65535";
                }
            }
            leaf Ip-Src {
                type inet:ip-prefix;
            }
            leaf Ip-Dst {
                type inet:ip-prefix;
            }
            leaf Port-Src {
                type inet:port-number;
            }
            leaf Port-Dst {
                type inet:port-number;
            }
            leaf Ip-Version {
                type inet:ip-version;
            }
	        leaf Ip-Protocol {
	            type enumeration {
	    	        enum "TCP" {
		                value 6;
		                description "TCP Protocol";
		        }
		            enum "UDP" {
		                value 17;
		                description "UDP Protocol";
		            }
	            }
	        }
            leaf timeOut {
                type uint32;
            }
        }
        output {
            leaf result {
                type string;
             }
         }

    }


    rpc register-subscriber-basic-info {
        description "Register about subscriber Id and other basic information.";
        input {
            leaf subId {
                type uint32 {
                    range "1 .. 65535";
                }
            }
            leaf fname {
                type string;
            }
            leaf lname {
                type string;
            }
            leaf address {
                type string;
            }
        }
        output {
            leaf result {
                type string;
            }
        }
    }


        rpc hello-world {
            input {
                leaf name {
                    type string;
                }
                leaf age {
                    type uint32;
                }
            }
            output {
                leaf greeting {
                    type string;
                }
            }
        }
            container greeting-registry {
                list greeting-registry-entry {
                    key "name";
                    leaf name {
                        type string;
                    }
                    leaf greeting {
                        type string;
                    }
                }
            }


            rpc subscriber-affected {

                input {
                    leaf nodeName {
                        type string;
                    }
                }
                output {
                    leaf-list subscriber-affected {
                        type uint32;
                    }
                }
            }

}
